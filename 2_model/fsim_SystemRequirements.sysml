// =========================================================================
// Requirements, function breakdown, R2F allocation matrices and the
// Requirements Verification Matrix, as held in fsim_Design_v5.xlsx.
//
// GENERATED by tools/xlsx_to_sysml.py - do not edit by hand.
// The workbook is the authority; re-run the generator after any change
// to it, so the model cannot drift from the requirements baseline.
//
// Notation follows the supplied reference examples:
//   * workbook IDs as SysML v2 short names <'...'>  (HSUVRequirements)
//   * L1 grouping its L2 children by `require`      (HSUVRequirements)
//   * satisfaction inside a context part            (RequirementDerivation)
// =========================================================================

package FlightSimulator_SystemRequirements {
    public import ScalarValues::*;

    doc /* Requirements baseline, workbook sheet 'Requirements'.
     * The L1 requirements group their L2 children by reference
     * (`require <child>;`) */

    enum def VerificationMethod {
        doc /* Workbook V-Method column: T = Test (automated
         * regression suite), I = Inspection, D = Demonstration. */
        enum test;
        enum inspection;
        enum demonstration;
    }

    requirement def SystemRequirement {
        doc /* Common shape of every requirement in the baseline. */
        attribute vMethod : VerificationMethod[0..*];
    }

    // ---- Level 2: constraining the logical blocks -------------------
    requirement <'L2SYS-REQ-01.01'> comprisePhysicalHOTASHandsThrottleStick : SystemRequirement {
        doc /* The system shall comprise a physical HOTAS
         * (Hands-On-Throttle-And-Stick). */
        attribute :>> vMethod = (VerificationMethod::inspection);
    }

    requirement <'L2SYS-REQ-01.01b'> HOTASContinuouslyPollPhysicalJoystickAxesThrottleLever : SystemRequirement {
        doc /* The HOTAS shall continuously poll the physical joystick axes,
         * throttle lever and buttons, and transmit the associated signals via
         * UDP to the Virtual Ownship. */
        attribute :>> vMethod = (VerificationMethod::test);
    }

    requirement <'L2SYS-REQ-01.02'> compriseVirtualOwnship : SystemRequirement {
        doc /* The system shall comprise a Virtual Ownship. */
        attribute :>> vMethod = (VerificationMethod::test);
    }

    requirement <'L2SYS-REQ-01.02b'> virtualOwnshipComputeAircraftSPhysicalStatePosition : SystemRequirement {
        doc /* The Virtual Ownship shall compute the aircraft's physical state
         * (position, attitude, velocity) at a 120Hz frequency based on
         * received control inputs. */
        attribute :>> vMethod = (VerificationMethod::test);
    }

    requirement <'L2SYS-REQ-01.03'> compriseVisual : SystemRequirement {
        doc /* The system shall comprise a Visual System. */
        attribute :>> vMethod = (VerificationMethod::inspection);
    }

    requirement <'L2SYS-REQ-01.03b'> visualRender3DExternalViewDrivenNativeFlightGear : SystemRequirement {
        doc /* The Visual System shall render a 3D external view driven by the
         * native-FlightGear UDP telemetry stream. */
        attribute :>> vMethod = (VerificationMethod::inspection);
    }

    requirement <'L2SYS-REQ-01.04'> initializeVirtualOwnshipGroundUserSelectedAirportConfigurable : SystemRequirement {
        doc /* The system shall initialize the Virtual Ownship on ground at a
         * user-selected airport from a configurable airport list. */
        attribute :>> vMethod = (VerificationMethod::test);
    }

    requirement <'L2SYS-REQ-01.04b'> airportSelectionChangeableOnlyDuringFlightFreeze : SystemRequirement {
        doc /* The airport selection shall be changeable only during flight-freeze. */
        attribute :>> vMethod = (VerificationMethod::test);
    }

    requirement <'L2SYS-REQ-01.05'> provideOutWindowOTWCameraViewOwnship : SystemRequirement {
        doc /* The system shall provide an Out-of-The-Window (OTW) camera view of
         * the ownship. */
        attribute :>> vMethod = (VerificationMethod::inspection);
    }

    requirement <'L2SYS-REQ-01.05b'> OTWCameraViewConsistentSelectedAircraftModelPosition : SystemRequirement {
        doc /* The OTW camera view shall be consistent with the selected aircraft
         * model and the position of the aircraft at any given t_sim
         * (simulation time). */
        attribute :>> vMethod = (VerificationMethod::inspection);
    }

    requirement <'L2SYS-REQ-01.06'> PCSProvideControlsPanel : SystemRequirement {
        doc /* The PCS shall provide a System Controls Panel. */
        attribute :>> vMethod = (VerificationMethod::test);
    }

    requirement <'L2SYS-REQ-01.06b'> provideEngineStartStopFunctionCommandedPilotENGINE : SystemRequirement {
        doc /* The system shall provide an “Engine start/stop” function, commanded
         * by the pilot via the ENGINE toggle-button in the System Controls
         * Panel (ON/OFF). */
        attribute :>> vMethod = (VerificationMethod::test);
    }

    requirement <'L2SYS-REQ-01.06c'> provideParkBrakeFunctionCommandedPilotPARKBRAKE : SystemRequirement {
        doc /* The system shall provide a “Park Brake” function, commanded by the
         * pilot via the PARK BRAKE toggle-button in the System Controls Panel
         * (ON/OFF). */
        attribute :>> vMethod = (VerificationMethod::test);
    }

    requirement <'L2SYS-REQ-01.06d'> provideAirBrakeFunctionCommandedPilotAIRBRAKE : SystemRequirement {
        doc /* The system shall provide an “Air Brake” function, commanded by the
         * pilot via the AIR BRAKE toggle-button in the System Controls Panel
         * (ON/OFF). */
        attribute :>> vMethod = (VerificationMethod::test);
    }

    requirement <'L2SYS-REQ-01.06e'> provideLandingGearFunctionCommandedPilotLDGGEAR : SystemRequirement {
        doc /* The system shall provide a “Landing Gear” function, commanded by the
         * pilot via the LDG GEAR toggle-button in the System Controls Panel
         * (UP/DOWN). */
        attribute :>> vMethod = (VerificationMethod::test);
    }

    requirement <'L2SYS-REQ-01.07'> virtualOwnshipEngineInitializeOFFZeroFuelConsumption : SystemRequirement {
        doc /* The Virtual Ownship engine shall initialize OFF with zero fuel
         * consumption. Upon engine start command (ENGINE set to ON) with
         * throttle at idle, the engine shall spool to idle and fuel
         * consumption shall commence. */
        attribute :>> vMethod = (VerificationMethod::test);
    }

    requirement <'L2SYS-REQ-01.08'> provideVirtualCockpitConsolePilotAkaPCSOr : SystemRequirement {
        doc /* The system shall provide a virtual cockpit console for the pilot,
         * aka PCS or Pilot Control Station. */
        attribute :>> vMethod = (VerificationMethod::test);
    }

    requirement <'L2SYS-REQ-01.08b'> PCSProvideScreenVirtualFlightControlsStickThrottle : SystemRequirement {
        doc /* The PCS shall provide on-screen virtual flight controls (stick,
         * throttle, pedals) usable when the physical HOTAS is absent; physical
         * HOTAS input shall take precedence when present. */
        attribute :>> vMethod = (VerificationMethod::test);
    }

    requirement <'L2SYS-REQ-01.08c'> PCSProvideScreenVirtualFlightGaugesDisplaysMinimum : SystemRequirement {
        doc /* The PCS shall provide on-screen virtual flight gauges and displays -
         * minimum: Airspeed, Attitude, Fuel, Heading, RPM, HUD view, Attention
         * Getters, and Message Window. */
        attribute :>> vMethod = (VerificationMethod::test, VerificationMethod::inspection);
    }

    requirement <'L2SYS-REQ-01.10'> PCSProvideSimControlPanelSelectionSSFSimulation : SystemRequirement {
        doc /* The PCS shall provide a Sim Control Panel for the selection of SSF
         * (Simulation Specific Functions) */
        attribute :>> vMethod = (VerificationMethod::test);
    }

    requirement <'L2SYS-REQ-01.10b'> supportFollowingSSFAccordingARINC610RUNSIM : SystemRequirement {
        doc /* The system shall support the following SSF, according to ARINC 610:
         * “RUN SIM”: start/resume simulation. “PAUSE SIM”: pause simulation
         * (flight-freeze). “RESET SIM”: reset simulation to initial state
         * (t0). “LAUNCH 3D OTW”: launch FlightGear engine and associated
         * aircraft camera view. “SET POSITION”: set aircraft position as Lat,
         * Lon (deg), Altitude (m), Speed (m/s), Heading (deg). “SAVE SNAPSHOT”
         * / “LOAD SNAPSHOT”: save/restore full simulation state. “FUEL
         * FREEZE”: hold tank contents constant. “TELEMETRY CAPTURE”: log
         * telemetry to CSV file. */
        attribute :>> vMethod = (VerificationMethod::test);
    }

    requirement <'L2SYS-REQ-01.11'> PCSProvideNavigationControlsPanelSettingAutopilotTargets : SystemRequirement {
        doc /* The PCS shall provide a Navigation Controls Panel for setting the
         * autopilot targets - Altitude (m), Speed (m/s), Heading (deg) - and
         * for engaging/disengaging the AP (heading hold), AH (altitude hold)
         * and AT (autothrottle) modes. */
        attribute :>> vMethod = (VerificationMethod::test);
    }

    requirement <'L2SYS-REQ-02.01'> tactical2DMapFetchRenderOpenStreetMapTilesCorrespondingAircraftS : SystemRequirement {
        doc /* The Tactical2DMap shall fetch and render OpenStreetMap tiles
         * corresponding to the aircraft's current GPS coordinates. */
        attribute :>> vMethod = (VerificationMethod::test, VerificationMethod::inspection);
    }

    requirement <'L2SYS-REQ-02.03'> PCSReceiveThreatDetectionsIncomingSyntheticEnvironment : SystemRequirement {
        doc /* The PCS shall receive the threat detections incoming from the
         * Synthetic Environment. */
        attribute :>> vMethod = (VerificationMethod::test);
    }

    requirement <'L2SYS-REQ-02.03b'> tactical2DMapDisplayThreatDetectionsCommunicatedPCSScaledColor : SystemRequirement {
        doc /* The Tactical2DMap shall display the threat detections, as
         * communicated by the PCS, as scaled, color-coded rings on the
         * tactical map. */
        attribute :>> vMethod = (VerificationMethod::test);
    }

    requirement <'L2SYS-REQ-02.04'> PCSDisplayGroundProximityAttentionGetterEG : SystemRequirement {
        doc /* The PCS shall display a ground-proximity attention getter (e.g.
         * 'PULL UP') when height above ground and vertical speed indicate
         * imminent ground impact. Attention Getter shall flash intermittently
         * while warning condition persists. */
        attribute :>> vMethod = (VerificationMethod::test);
    }

    requirement <'L2SYS-REQ-03.01'> compriseSyntheticEnvironmentSimulationExternalEntitiesSimulatedScenario : SystemRequirement {
        doc /* The system shall comprise a Synthetic Environment for the simulation
         * of external entities in the simulated scenario. */
        attribute :>> vMethod = (VerificationMethod::test);
    }

    requirement <'L2SYS-REQ-03.02'> syntheticEnvironmentProvideInterfaceGUISpawnClassifyFRIEND : SystemRequirement {
        doc /* The Synthetic Environment shall provide an interface (GUI) to spawn
         * and classify (FRIEND, FOE, UNKNOWN) radar emitters with defined
         * maximum ranges. */
        attribute :>> vMethod = (VerificationMethod::test);
    }

    requirement <'L2SYS-REQ-03.03'> syntheticEnvironmentGUIAllowInstructorSetAdjustBeacon : SystemRequirement {
        doc /* The Synthetic Environment GUI shall allow the instructor to set and
         * adjust, for each beacon, the emitter parameters of the radar
         * equation (transmit power, antenna gain, frequency, receiver
         * sensitivity). */
        attribute :>> vMethod = (VerificationMethod::test);
    }

    requirement <'L2SYS-REQ-03.04'> syntheticEnvironmentGUIAllowInstructorSetAdjustOwnship : SystemRequirement {
        doc /* The Synthetic Environment GUI shall allow the instructor to set and
         * adjust the ownship radar cross section as a scenario parameter. */
        attribute :>> vMethod = (VerificationMethod::test);
    }

    requirement <'L2SYS-REQ-03.05'> syntheticEnvironmentComputeBeaconSDetectionStatusEvaluating : SystemRequirement {
        doc /* The Synthetic Environment shall compute each beacon's detection
         * status by evaluating the monostatic radar equation against the
         * received ownship state. */
        attribute :>> vMethod = (VerificationMethod::test);
    }

    requirement <'L2SYS-REQ-04.01'> busManagerOrchestrateExchangeStateVariablesBetweenTacticalDatabus : SystemRequirement {
        doc /* The BusManager shall orchestrate the exchange of state variables
         * between the tactical databus and external UDP ports without blocking
         * the Python execution threads. */
        attribute :>> vMethod = (VerificationMethod::test);
    }

    requirement <'L2SYS-REQ-05.01'> integrateFlightGearCOTSFlightSimulatorOTWVisualEngine : SystemRequirement {
        doc /* The system shall integrate FlightGear as the COTS flight simulator
         * (OTW visual engine). */
        attribute :>> vMethod = (VerificationMethod::demonstration);
    }

    requirement <'L2SYS-REQ-05.02'> integrateOpenStreetMapTileServiceTactical2DMap : SystemRequirement {
        doc /* The system shall integrate the OpenStreetMap tile service for the
         * Tactical2DMap. */
        attribute :>> vMethod = (VerificationMethod::demonstration);
    }

    // ---- Stable aliases ---------------------------------------------
    // Element names are DERIVED from the requirement text, so a
    // workbook rewording changes them. Any hand-authored file that
    // references a requirement should use the alias below, which is
    // the workbook ID and never changes.
    alias L1SYS_REQ_01 for provideRealTimeFlightControlPhysicalDynamicsSimulation;
    alias L1SYS_REQ_02 for provideGeographicPositioningThreatDetectionAwarenessPilot;
    alias L1SYS_REQ_03 for allowInstructorManageSimulatedElectronicWarfareThreats;
    alias L1SYS_REQ_04 for synchronizeDataAcrossAllDistributedSubSystemsMaintain;
    alias L1SYS_REQ_05 for ableIntegrateExternalSWComponentsCOTSAPIsDatabases;
    alias L2SYS_REQ_01_01 for comprisePhysicalHOTASHandsThrottleStick;
    alias L2SYS_REQ_01_01b for HOTASContinuouslyPollPhysicalJoystickAxesThrottleLever;
    alias L2SYS_REQ_01_02 for compriseVirtualOwnship;
    alias L2SYS_REQ_01_02b for virtualOwnshipComputeAircraftSPhysicalStatePosition;
    alias L2SYS_REQ_01_03 for compriseVisual;
    alias L2SYS_REQ_01_03b for visualRender3DExternalViewDrivenNativeFlightGear;
    alias L2SYS_REQ_01_04 for initializeVirtualOwnshipGroundUserSelectedAirportConfigurable;
    alias L2SYS_REQ_01_04b for airportSelectionChangeableOnlyDuringFlightFreeze;
    alias L2SYS_REQ_01_05 for provideOutWindowOTWCameraViewOwnship;
    alias L2SYS_REQ_01_05b for OTWCameraViewConsistentSelectedAircraftModelPosition;
    alias L2SYS_REQ_01_06 for PCSProvideControlsPanel;
    alias L2SYS_REQ_01_06b for provideEngineStartStopFunctionCommandedPilotENGINE;
    alias L2SYS_REQ_01_06c for provideParkBrakeFunctionCommandedPilotPARKBRAKE;
    alias L2SYS_REQ_01_06d for provideAirBrakeFunctionCommandedPilotAIRBRAKE;
    alias L2SYS_REQ_01_06e for provideLandingGearFunctionCommandedPilotLDGGEAR;
    alias L2SYS_REQ_01_07 for virtualOwnshipEngineInitializeOFFZeroFuelConsumption;
    alias L2SYS_REQ_01_08 for provideVirtualCockpitConsolePilotAkaPCSOr;
    alias L2SYS_REQ_01_08b for PCSProvideScreenVirtualFlightControlsStickThrottle;
    alias L2SYS_REQ_01_08c for PCSProvideScreenVirtualFlightGaugesDisplaysMinimum;
    alias L2SYS_REQ_01_10 for PCSProvideSimControlPanelSelectionSSFSimulation;
    alias L2SYS_REQ_01_10b for supportFollowingSSFAccordingARINC610RUNSIM;
    alias L2SYS_REQ_01_11 for PCSProvideNavigationControlsPanelSettingAutopilotTargets;
    alias L2SYS_REQ_02_01 for tactical2DMapFetchRenderOpenStreetMapTilesCorrespondingAircraftS;
    alias L2SYS_REQ_02_03 for PCSReceiveThreatDetectionsIncomingSyntheticEnvironment;
    alias L2SYS_REQ_02_03b for tactical2DMapDisplayThreatDetectionsCommunicatedPCSScaledColor;
    alias L2SYS_REQ_02_04 for PCSDisplayGroundProximityAttentionGetterEG;
    alias L2SYS_REQ_03_01 for compriseSyntheticEnvironmentSimulationExternalEntitiesSimulatedScenario;
    alias L2SYS_REQ_03_02 for syntheticEnvironmentProvideInterfaceGUISpawnClassifyFRIEND;
    alias L2SYS_REQ_03_03 for syntheticEnvironmentGUIAllowInstructorSetAdjustBeacon;
    alias L2SYS_REQ_03_04 for syntheticEnvironmentGUIAllowInstructorSetAdjustOwnship;
    alias L2SYS_REQ_03_05 for syntheticEnvironmentComputeBeaconSDetectionStatusEvaluating;
    alias L2SYS_REQ_04_01 for busManagerOrchestrateExchangeStateVariablesBetweenTacticalDatabus;
    alias L2SYS_REQ_05_01 for integrateFlightGearCOTSFlightSimulatorOTWVisualEngine;
    alias L2SYS_REQ_05_02 for integrateOpenStreetMapTileServiceTactical2DMap;

    // ---- Level 1: grouping their L2 children by reference -----------
    requirement <'L1SYS-REQ-01'> provideRealTimeFlightControlPhysicalDynamicsSimulation {
        doc /* The system shall provide real-time flight control and physical
         * dynamics simulation for the pilot. */
        require comprisePhysicalHOTASHandsThrottleStick;
        require HOTASContinuouslyPollPhysicalJoystickAxesThrottleLever;
        require compriseVirtualOwnship;
        require virtualOwnshipComputeAircraftSPhysicalStatePosition;
        require compriseVisual;
        require visualRender3DExternalViewDrivenNativeFlightGear;
        require initializeVirtualOwnshipGroundUserSelectedAirportConfigurable;
        require airportSelectionChangeableOnlyDuringFlightFreeze;
        require provideOutWindowOTWCameraViewOwnship;
        require OTWCameraViewConsistentSelectedAircraftModelPosition;
        require PCSProvideControlsPanel;
        require provideEngineStartStopFunctionCommandedPilotENGINE;
        require provideParkBrakeFunctionCommandedPilotPARKBRAKE;
        require provideAirBrakeFunctionCommandedPilotAIRBRAKE;
        require provideLandingGearFunctionCommandedPilotLDGGEAR;
        require virtualOwnshipEngineInitializeOFFZeroFuelConsumption;
        require provideVirtualCockpitConsolePilotAkaPCSOr;
        require PCSProvideScreenVirtualFlightControlsStickThrottle;
        require PCSProvideScreenVirtualFlightGaugesDisplaysMinimum;
        require PCSProvideSimControlPanelSelectionSSFSimulation;
        require supportFollowingSSFAccordingARINC610RUNSIM;
        require PCSProvideNavigationControlsPanelSettingAutopilotTargets;
    }

    requirement <'L1SYS-REQ-02'> provideGeographicPositioningThreatDetectionAwarenessPilot {
        doc /* The system shall provide geographic positioning and threat detection
         * awareness to the pilot. */
        require tactical2DMapFetchRenderOpenStreetMapTilesCorrespondingAircraftS;
        require PCSReceiveThreatDetectionsIncomingSyntheticEnvironment;
        require tactical2DMapDisplayThreatDetectionsCommunicatedPCSScaledColor;
        require PCSDisplayGroundProximityAttentionGetterEG;
    }

    requirement <'L1SYS-REQ-03'> allowInstructorManageSimulatedElectronicWarfareThreats {
        doc /* The system shall allow an instructor to manage simulated electronic
         * warfare threats. */
        require compriseSyntheticEnvironmentSimulationExternalEntitiesSimulatedScenario;
        require syntheticEnvironmentProvideInterfaceGUISpawnClassifyFRIEND;
        require syntheticEnvironmentGUIAllowInstructorSetAdjustBeacon;
        require syntheticEnvironmentGUIAllowInstructorSetAdjustOwnship;
        require syntheticEnvironmentComputeBeaconSDetectionStatusEvaluating;
    }

    requirement <'L1SYS-REQ-04'> synchronizeDataAcrossAllDistributedSubSystemsMaintain {
        doc /* The system shall synchronize data across all distributed sub-systems
         * to maintain a cohesive simulation state. */
        require busManagerOrchestrateExchangeStateVariablesBetweenTacticalDatabus;
    }

    requirement <'L1SYS-REQ-05'> ableIntegrateExternalSWComponentsCOTSAPIsDatabases {
        doc /* The system shall be able to integrate external SW components (COTS,
         * APIs, databases and libraries). */
        require integrateFlightGearCOTSFlightSimulatorOTWVisualEngine;
        require integrateOpenStreetMapTileServiceTactical2DMap;
    }

}
