// =========================================================================
// Requirements, function breakdown, R2F allocation matrices and the
// Requirements Verification Matrix, as held in fsim_Design_v5.xlsx.
//
// GENERATED by tools/xlsx_to_sysml.py - do not edit by hand.
// The workbook is the authority; re-run the generator after any change
// to it, so the model cannot drift from the requirements baseline.
//
// Notation follows the supplied reference examples:
//   * workbook IDs as SysML v2 short names <'...'>  (HSUVRequirements)
//   * L1 grouping its L2 children by `require`      (HSUVRequirements)
//   * satisfaction inside a context part            (RequirementDerivation)
// =========================================================================

package FlightSimulator_Functions {
    public import ScalarValues::*;

    doc /* System function breakdown, workbook sheet 'Functions'.
     * L1 = system level, L2 = sub-system level. Modelled as action
     * defs because a function is behaviour.
     *
     * The workbook ID is the SysML v2 SHORT NAME <'...'>, so tools
     * render it beside the element; */

    action def <'L1SYS-FCN-01'> ProvideFlightControlDynamics {
        doc /* Provide Flight Control & Dynamics */

        action def <'L2SYS-FCN-01.1'> CapturePhysicalPilotHardwareInputs {
            doc /* Capture physical pilot hardware inputs. */
        }

        action def <'L2SYS-FCN-01.2'> Compute6DoFFlightPhysics {
            doc /* Compute 6-DoF flight physics and telemetry. */
        }

        action def <'L2SYS-FCN-01.3'> Render3DOutWindowOTW {
            doc /* Render 3D Out-The-Window (OTW) visual environment. */
        }

        action def <'L2SYS-FCN-01.4'> InitializeOwnshipGroundUserSelected {
            doc /* Initialize ownship on ground at a user-selected airport
             * (list-configurable, freeze-gated). */
        }

        action def <'L2SYS-FCN-01.5'> LaunchOTWVisualViewConsistent {
            doc /* Launch OTW visual view consistent with the selected airport and
             * aircraft model. */
        }

        action def <'L2SYS-FCN-01.6'> CommandAircraftSystemsEngineStart {
            doc /* Command aircraft systems (engine start/stop, park brake, air brake,
             * landing gear) from the pilot UI. */
        }

        action def <'L2SYS-FCN-01.7'> ManageEngineStateOffIdle {
            doc /* Manage engine state (off/idle/running) and fuel consumption. */
        }

        action def <'L2SYS-FCN-01.8'> ProvidePilotControlStationUI {
            doc /* Provide the pilot control station UI (virtual cockpit console:
             * panels, gauges, virtual controls, message window). */
        }
    }

    action def <'L1SYS-FCN-02'> ProvideTacticalSituationalAwareness {
        doc /* Provide Tactical Situational Awareness */

        action def <'L2SYS-FCN-02.1'> RenderRealTimeGeographic2D {
            doc /* Render real-time geographic 2D map. */
        }

        action def <'L2SYS-FCN-02.2'> CalculateRadarSlantRangeDetection {
            doc /* Calculate radar slant range and detection envelopes. */
        }

        action def <'L2SYS-FCN-02.3'> DisplayDynamicThreatRingsAircraft {
            doc /* Display dynamic threat rings and aircraft telemetry. */
        }

        action def <'L2SYS-FCN-02.4'> MonitorGroundProximityAlertPilot {
            doc /* Monitor ground proximity and alert the pilot (attention getter). */
        }
    }

    action def <'L1SYS-FCN-03'> ManageSimulationScenario {
        doc /* Manage Simulation Scenario */

        action def <'L2SYS-FCN-03.1'> InjectConfigureSyntheticRadarEmitters {
            doc /* Inject and configure synthetic radar emitters. */
        }

        action def <'L2SYS-FCN-03.2'> ConfigurePerBeaconRadarEquation {
            doc /* Configure per-beacon radar-equation emitter parameters (Pt, G, f,
             * Pmin). */
        }

        action def <'L2SYS-FCN-03.3'> ConfigureOwnshipRadarCrossSection {
            doc /* Configure ownship radar cross section as a scenario parameter. */
        }
    }

    action def <'L1SYS-FCN-04'> SynchronizeDistributed {
        doc /* Synchronize Distributed System */

        action def <'L2SYS-FCN-04.1'> RouteTelemetryTacticalObjectsAcross {
            doc /* Route telemetry and tactical objects across the databus. */
        }
    }

    action def <'L1SYS-FCN-05'> IntegrateExternalSWComponents {
        doc /* Integrate External SW Components */

        action def <'L2SYS-FCN-05.1'> IntegrateCOTSFlightSimulatorFlightGear {
            doc /* Integrate the COTS flight simulator (FlightGear) as OTW visual
             * engine. */
        }

        action def <'L2SYS-FCN-05.2'> IntegrateOpenStreetMapTileServiceTactical {
            doc /* Integrate the OpenStreetMap tile service for the tactical map. */
        }
    }

}
