// =========================================================================
// Requirements, function breakdown, R2F allocation matrices and the
// Requirements Verification Matrix, as held in fsim_Design_v5.xlsx.
//
// GENERATED by tools/xlsx_to_sysml.py - do not edit by hand.
// The workbook is the authority; re-run the generator after any change
// to it, so the model cannot drift from the requirements baseline.
//
// Notation follows the supplied reference examples:
//   * workbook IDs as SysML v2 short names <'...'>  (HSUVRequirements)
//   * L1 grouping its L2 children by `require`      (HSUVRequirements)
//   * satisfaction inside a context part            (RequirementDerivation)
// =========================================================================

package FlightSimulator_R2F {
    private import FlightSimulator_Functions::*;
    private import FlightSimulator_SystemRequirements::*;
    private import FlightSimulator_TA_System::*;

    doc /* Requirement-to-Function allocation (workbook sheets
     * 'R2F_L1_AllocationMtx' and 'R2F_L2_AllocationMtx') and the
     * 'Allocated Logical Block' column expressed as satisfaction.
     *
     * NOTE 1: each satisfy usage is NAMED. The anonymous form
     * (`satisfy <req> by <part>;`) creates an unnamed element, which
     * renders as an empty "«feature» noname" box - reported from
     * the target toolchain. Pass --satisfy-style anonymous to get
     * the short form back if your tool prefers it.
     *
     * NOTE 2: `satisfy ... by ...`
     * needs a part USAGE, not a part def. The RequirementDerivation
     * example makes the same point by placing its satisfies inside
     * `part satisfactionContext`. The workbook names logical BLOCKS
     * (defs); each is resolved here to the usage that realizes it in
     * the TA assembly. */

    // ---- L1 --------------------------------------------------------
    dependency alloc_L1SYS_REQ_01
        from provideRealTimeFlightControlPhysicalDynamicsSimulation
        to   ProvideFlightControlDynamics;
    dependency alloc_L1SYS_REQ_02
        from provideGeographicPositioningThreatDetectionAwarenessPilot
        to   ProvideTacticalSituationalAwareness;
    dependency alloc_L1SYS_REQ_03
        from allowInstructorManageSimulatedElectronicWarfareThreats
        to   ManageSimulationScenario;
    dependency alloc_L1SYS_REQ_04
        from synchronizeDataAcrossAllDistributedSubSystemsMaintain
        to   SynchronizeDistributed;
    dependency alloc_L1SYS_REQ_05
        from ableIntegrateExternalSWComponentsCOTSAPIsDatabases
        to   IntegrateExternalSWComponents;

    // ---- L2 --------------------------------------------------------
    dependency alloc_L2SYS_REQ_01_01
        from comprisePhysicalHOTASHandsThrottleStick
        to   ProvideFlightControlDynamics::CapturePhysicalPilotHardwareInputs;
    dependency alloc_L2SYS_REQ_01_01b
        from HOTASContinuouslyPollPhysicalJoystickAxesThrottleLever
        to   ProvideFlightControlDynamics::CapturePhysicalPilotHardwareInputs;
    dependency alloc_L2SYS_REQ_01_02
        from compriseVirtualOwnship
        to   ProvideFlightControlDynamics::Compute6DoFFlightPhysics;
    dependency alloc_L2SYS_REQ_01_02b
        from virtualOwnshipComputeAircraftSPhysicalStatePosition
        to   ProvideFlightControlDynamics::Compute6DoFFlightPhysics;
    dependency alloc_L2SYS_REQ_01_03
        from compriseVisual
        to   ProvideFlightControlDynamics::Render3DOutWindowOTW;
    dependency alloc_L2SYS_REQ_01_03b
        from visualRender3DExternalViewDrivenNativeFlightGear
        to   ProvideFlightControlDynamics::Render3DOutWindowOTW;
    dependency alloc_L2SYS_REQ_01_04
        from initializeVirtualOwnshipGroundUserSelectedAirportConfigurable
        to   ProvideFlightControlDynamics::InitializeOwnshipGroundUserSelected;
    dependency alloc_L2SYS_REQ_01_04b
        from airportSelectionChangeableOnlyDuringFlightFreeze
        to   ProvideFlightControlDynamics::InitializeOwnshipGroundUserSelected;
    dependency alloc_L2SYS_REQ_01_05
        from provideOutWindowOTWCameraViewOwnship
        to   ProvideFlightControlDynamics::LaunchOTWVisualViewConsistent;
    dependency alloc_L2SYS_REQ_01_05b
        from OTWCameraViewConsistentSelectedAircraftModelPosition
        to   ProvideFlightControlDynamics::LaunchOTWVisualViewConsistent;
    dependency alloc_L2SYS_REQ_01_06
        from PCSProvideControlsPanel
        to   ProvideFlightControlDynamics::CommandAircraftSystemsEngineStart;
    dependency alloc_L2SYS_REQ_01_06b
        from provideEngineStartStopFunctionCommandedPilotENGINE
        to   ProvideFlightControlDynamics::CommandAircraftSystemsEngineStart;
    dependency alloc_L2SYS_REQ_01_06c
        from provideParkBrakeFunctionCommandedPilotPARKBRAKE
        to   ProvideFlightControlDynamics::CommandAircraftSystemsEngineStart;
    dependency alloc_L2SYS_REQ_01_06d
        from provideAirBrakeFunctionCommandedPilotAIRBRAKE
        to   ProvideFlightControlDynamics::CommandAircraftSystemsEngineStart;
    dependency alloc_L2SYS_REQ_01_06e
        from provideLandingGearFunctionCommandedPilotLDGGEAR
        to   ProvideFlightControlDynamics::CommandAircraftSystemsEngineStart;
    dependency alloc_L2SYS_REQ_01_07
        from virtualOwnshipEngineInitializeOFFZeroFuelConsumption
        to   ProvideFlightControlDynamics::ManageEngineStateOffIdle;
    dependency alloc_L2SYS_REQ_01_08
        from provideVirtualCockpitConsolePilotAkaPCSOr
        to   ProvideFlightControlDynamics::ProvidePilotControlStationUI;
    dependency alloc_L2SYS_REQ_01_08b
        from PCSProvideScreenVirtualFlightControlsStickThrottle
        to   ProvideFlightControlDynamics::ProvidePilotControlStationUI;
    dependency alloc_L2SYS_REQ_01_08c
        from PCSProvideScreenVirtualFlightGaugesDisplaysMinimum
        to   ProvideFlightControlDynamics::ProvidePilotControlStationUI;
    dependency alloc_L2SYS_REQ_01_10
        from PCSProvideSimControlPanelSelectionSSFSimulation
        to   ProvideFlightControlDynamics::ProvidePilotControlStationUI;
    dependency alloc_L2SYS_REQ_01_10b
        from supportFollowingSSFAccordingARINC610RUNSIM
        to   ProvideFlightControlDynamics::ProvidePilotControlStationUI;
    dependency alloc_L2SYS_REQ_01_11
        from PCSProvideNavigationControlsPanelSettingAutopilotTargets
        to   ProvideFlightControlDynamics::ProvidePilotControlStationUI;
    dependency alloc_L2SYS_REQ_02_01
        from tactical2DMapFetchRenderOpenStreetMapTilesCorrespondingAircraftS
        to   ProvideTacticalSituationalAwareness::RenderRealTimeGeographic2D;
    dependency alloc_L2SYS_REQ_02_03
        from PCSReceiveThreatDetectionsIncomingSyntheticEnvironment
        to   ProvideTacticalSituationalAwareness::DisplayDynamicThreatRingsAircraft;
    dependency alloc_L2SYS_REQ_02_03b
        from tactical2DMapDisplayThreatDetectionsCommunicatedPCSScaledColor
        to   ProvideTacticalSituationalAwareness::DisplayDynamicThreatRingsAircraft;
    dependency alloc_L2SYS_REQ_02_04
        from PCSDisplayGroundProximityAttentionGetterEG
        to   ProvideTacticalSituationalAwareness::MonitorGroundProximityAlertPilot;
    dependency alloc_L2SYS_REQ_03_01
        from compriseSyntheticEnvironmentSimulationExternalEntitiesSimulatedScenario
        to   ManageSimulationScenario::InjectConfigureSyntheticRadarEmitters;
    dependency alloc_L2SYS_REQ_03_02
        from syntheticEnvironmentProvideInterfaceGUISpawnClassifyFRIEND
        to   ManageSimulationScenario::InjectConfigureSyntheticRadarEmitters;
    dependency alloc_L2SYS_REQ_03_03
        from syntheticEnvironmentGUIAllowInstructorSetAdjustBeacon
        to   ManageSimulationScenario::ConfigurePerBeaconRadarEquation;
    dependency alloc_L2SYS_REQ_03_04
        from syntheticEnvironmentGUIAllowInstructorSetAdjustOwnship
        to   ManageSimulationScenario::ConfigureOwnshipRadarCrossSection;
    dependency alloc_L2SYS_REQ_03_05
        from syntheticEnvironmentComputeBeaconSDetectionStatusEvaluating
        to   ProvideTacticalSituationalAwareness::CalculateRadarSlantRangeDetection;
    dependency alloc_L2SYS_REQ_04_01
        from busManagerOrchestrateExchangeStateVariablesBetweenTacticalDatabus
        to   SynchronizeDistributed::RouteTelemetryTacticalObjectsAcross;
    dependency alloc_L2SYS_REQ_05_01
        from integrateFlightGearCOTSFlightSimulatorOTWVisualEngine
        to   IntegrateExternalSWComponents::IntegrateCOTSFlightSimulatorFlightGear;
    dependency alloc_L2SYS_REQ_05_02
        from integrateOpenStreetMapTileServiceTactical2DMap
        to   IntegrateExternalSWComponents::IntegrateOpenStreetMapTileServiceTactical;

    // ---- satisfaction, against real part usages ----------------------
    part fsimContext {
        doc /* Satisfaction context: holds the one FlightSimSystem
         * usage every `satisfy` below resolves against. */
        part fsim : FlightSimulator_TA_System::FlightSimSystem;

        satisfy requirement sat_01_01_Hotas :>> comprisePhysicalHOTASHandsThrottleStick by fsim.hotas;
        satisfy requirement sat_01_01b_Hotas :>> HOTASContinuouslyPollPhysicalJoystickAxesThrottleLever by fsim.hotas;
        satisfy requirement sat_01_02_VirtualOwnship :>> compriseVirtualOwnship by fsim.pcs.threadPhysics;
        satisfy requirement sat_01_02b_VirtualOwnship :>> virtualOwnshipComputeAircraftSPhysicalStatePosition by fsim.pcs.threadPhysics;
        satisfy requirement sat_01_03_VisualSystem :>> compriseVisual by fsim.fgfs;
        satisfy requirement sat_01_03b_VisualSystem :>> visualRender3DExternalViewDrivenNativeFlightGear by fsim.fgfs;
        satisfy requirement sat_01_04_PilotControlStation :>> initializeVirtualOwnshipGroundUserSelectedAirportConfigurable by fsim.pcs;
        satisfy requirement sat_01_04_VirtualOwnship :>> initializeVirtualOwnshipGroundUserSelectedAirportConfigurable by fsim.pcs.threadPhysics;
        satisfy requirement sat_01_04b_PilotControlStation :>> airportSelectionChangeableOnlyDuringFlightFreeze by fsim.pcs;
        satisfy requirement sat_01_05_PilotControlStation :>> provideOutWindowOTWCameraViewOwnship by fsim.pcs;
        satisfy requirement sat_01_05_VisualSystem :>> provideOutWindowOTWCameraViewOwnship by fsim.fgfs;
        satisfy requirement sat_01_05b_PilotControlStation :>> OTWCameraViewConsistentSelectedAircraftModelPosition by fsim.pcs;
        satisfy requirement sat_01_05b_VisualSystem :>> OTWCameraViewConsistentSelectedAircraftModelPosition by fsim.fgfs;
        satisfy requirement sat_01_06_PilotControlStation :>> PCSProvideControlsPanel by fsim.pcs;
        satisfy requirement sat_01_06b_PilotControlStation :>> provideEngineStartStopFunctionCommandedPilotENGINE by fsim.pcs;
        satisfy requirement sat_01_06b_VirtualOwnship :>> provideEngineStartStopFunctionCommandedPilotENGINE by fsim.pcs.threadPhysics;
        satisfy requirement sat_01_06c_PilotControlStation :>> provideParkBrakeFunctionCommandedPilotPARKBRAKE by fsim.pcs;
        satisfy requirement sat_01_06c_VirtualOwnship :>> provideParkBrakeFunctionCommandedPilotPARKBRAKE by fsim.pcs.threadPhysics;
        satisfy requirement sat_01_06d_PilotControlStation :>> provideAirBrakeFunctionCommandedPilotAIRBRAKE by fsim.pcs;
        satisfy requirement sat_01_06d_VirtualOwnship :>> provideAirBrakeFunctionCommandedPilotAIRBRAKE by fsim.pcs.threadPhysics;
        satisfy requirement sat_01_06e_PilotControlStation :>> provideLandingGearFunctionCommandedPilotLDGGEAR by fsim.pcs;
        satisfy requirement sat_01_06e_VirtualOwnship :>> provideLandingGearFunctionCommandedPilotLDGGEAR by fsim.pcs.threadPhysics;
        satisfy requirement sat_01_07_VirtualOwnship :>> virtualOwnshipEngineInitializeOFFZeroFuelConsumption by fsim.pcs.threadPhysics;
        satisfy requirement sat_01_08_PilotControlStation :>> provideVirtualCockpitConsolePilotAkaPCSOr by fsim.pcs;
        satisfy requirement sat_01_08b_PilotControlStation :>> PCSProvideScreenVirtualFlightControlsStickThrottle by fsim.pcs;
        satisfy requirement sat_01_08c_PilotControlStation :>> PCSProvideScreenVirtualFlightGaugesDisplaysMinimum by fsim.pcs;
        satisfy requirement sat_01_10_PilotControlStation :>> PCSProvideSimControlPanelSelectionSSFSimulation by fsim.pcs;
        satisfy requirement sat_01_10b_PilotControlStation :>> supportFollowingSSFAccordingARINC610RUNSIM by fsim.pcs;
        satisfy requirement sat_01_11_PilotControlStation :>> PCSProvideNavigationControlsPanelSettingAutopilotTargets by fsim.pcs;
        satisfy requirement sat_02_01_Tactical2DMap :>> tactical2DMapFetchRenderOpenStreetMapTilesCorrespondingAircraftS by fsim.pcs.threadMapWindow;
        satisfy requirement sat_02_03_PilotControlStation :>> PCSReceiveThreatDetectionsIncomingSyntheticEnvironment by fsim.pcs;
        satisfy requirement sat_02_03b_Tactical2DMap :>> tactical2DMapDisplayThreatDetectionsCommunicatedPCSScaledColor by fsim.pcs.threadMapWindow;
        satisfy requirement sat_02_04_PilotControlStation :>> PCSDisplayGroundProximityAttentionGetterEG by fsim.pcs;
        satisfy requirement sat_03_01_SyntheticEnvironment :>> compriseSyntheticEnvironmentSimulationExternalEntitiesSimulatedScenario by fsim.sem;
        satisfy requirement sat_03_02_SyntheticEnvironment :>> syntheticEnvironmentProvideInterfaceGUISpawnClassifyFRIEND by fsim.sem;
        satisfy requirement sat_03_03_SyntheticEnvironment :>> syntheticEnvironmentGUIAllowInstructorSetAdjustBeacon by fsim.sem;
        satisfy requirement sat_03_04_SyntheticEnvironment :>> syntheticEnvironmentGUIAllowInstructorSetAdjustOwnship by fsim.sem;
        satisfy requirement sat_03_05_SyntheticEnvironment :>> syntheticEnvironmentComputeBeaconSDetectionStatusEvaluating by fsim.sem;
        satisfy requirement sat_04_01_BusManager :>> busManagerOrchestrateExchangeStateVariablesBetweenTacticalDatabus by fsim.simbus;
        satisfy requirement sat_05_01_VisualSystem :>> integrateFlightGearCOTSFlightSimulatorOTWVisualEngine by fsim.fgfs;
        satisfy requirement sat_05_02_Tactical2DMap :>> integrateOpenStreetMapTileServiceTactical2DMap by fsim.pcs.threadMapWindow;
    }
}
