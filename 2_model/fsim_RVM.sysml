// =========================================================================
// Requirements, function breakdown, R2F allocation matrices and the
// Requirements Verification Matrix, as held in fsim_Design_v5.xlsx.
//
// GENERATED by tools/xlsx_to_sysml.py - do not edit by hand.
// The workbook is the authority; re-run the generator after any change
// to it, so the model cannot drift from the requirements baseline.
//
// Notation follows the supplied reference examples:
//   * workbook IDs as SysML v2 short names <'...'>  (HSUVRequirements)
//   * L1 grouping its L2 children by `require`      (HSUVRequirements)
//   * satisfaction inside a context part            (RequirementDerivation)
// =========================================================================

package FlightSimulator_RVM {
    private import FlightSimulator_SystemRequirements::*;

    doc /* Requirements Verification Matrix: one verification case
     * per L2 requirement, carrying the method the workbook assigns
     * it. V-Method T is realized by the pytest regression suite;
     * I and D by the manual checklist in
     * docs/MANUAL_VERIFICATION.md. */

    verification def VerifyByTest {
        doc /* Automated regression test, executed headless. */
    }
    verification def VerifyByInspection {
        doc /* Human inspection of the delivered system. */
    }
    verification def VerifyByDemonstration {
        doc /* Live demonstration on the target workstation. */
    }

    verification <'VC-01.01-I'> vcI_01_01 : VerifyByInspection {
        objective { verify comprisePhysicalHOTASHandsThrottleStick; }
    }
    verification <'VC-01.01b-T'> vcT_01_01b : VerifyByTest {
        objective { verify HOTASContinuouslyPollPhysicalJoystickAxesThrottleLever; }
    }
    verification <'VC-01.02-T'> vcT_01_02 : VerifyByTest {
        objective { verify compriseVirtualOwnship; }
    }
    verification <'VC-01.02b-T'> vcT_01_02b : VerifyByTest {
        objective { verify virtualOwnshipComputeAircraftSPhysicalStatePosition; }
    }
    verification <'VC-01.03-I'> vcI_01_03 : VerifyByInspection {
        objective { verify compriseVisual; }
    }
    verification <'VC-01.03b-I'> vcI_01_03b : VerifyByInspection {
        objective { verify visualRender3DExternalViewDrivenNativeFlightGear; }
    }
    verification <'VC-01.04-T'> vcT_01_04 : VerifyByTest {
        objective { verify initializeVirtualOwnshipGroundUserSelectedAirportConfigurable; }
    }
    verification <'VC-01.04b-T'> vcT_01_04b : VerifyByTest {
        objective { verify airportSelectionChangeableOnlyDuringFlightFreeze; }
    }
    verification <'VC-01.05-I'> vcI_01_05 : VerifyByInspection {
        objective { verify provideOutWindowOTWCameraViewOwnship; }
    }
    verification <'VC-01.05b-I'> vcI_01_05b : VerifyByInspection {
        objective { verify OTWCameraViewConsistentSelectedAircraftModelPosition; }
    }
    verification <'VC-01.06-T'> vcT_01_06 : VerifyByTest {
        objective { verify PCSProvideControlsPanel; }
    }
    verification <'VC-01.06b-T'> vcT_01_06b : VerifyByTest {
        objective { verify provideEngineStartStopFunctionCommandedPilotENGINE; }
    }
    verification <'VC-01.06c-T'> vcT_01_06c : VerifyByTest {
        objective { verify provideParkBrakeFunctionCommandedPilotPARKBRAKE; }
    }
    verification <'VC-01.06d-T'> vcT_01_06d : VerifyByTest {
        objective { verify provideAirBrakeFunctionCommandedPilotAIRBRAKE; }
    }
    verification <'VC-01.06e-T'> vcT_01_06e : VerifyByTest {
        objective { verify provideLandingGearFunctionCommandedPilotLDGGEAR; }
    }
    verification <'VC-01.07-T'> vcT_01_07 : VerifyByTest {
        objective { verify virtualOwnshipEngineInitializeOFFZeroFuelConsumption; }
    }
    verification <'VC-01.08-T'> vcT_01_08 : VerifyByTest {
        objective { verify provideVirtualCockpitConsolePilotAkaPCSOr; }
    }
    verification <'VC-01.08b-T'> vcT_01_08b : VerifyByTest {
        objective { verify PCSProvideScreenVirtualFlightControlsStickThrottle; }
    }
    verification <'VC-01.08c-T'> vcT_01_08c : VerifyByTest {
        objective { verify PCSProvideScreenVirtualFlightGaugesDisplaysMinimum; }
    }
    verification <'VC-01.08c-I'> vcI_01_08c : VerifyByInspection {
        objective { verify PCSProvideScreenVirtualFlightGaugesDisplaysMinimum; }
    }
    verification <'VC-01.10-T'> vcT_01_10 : VerifyByTest {
        objective { verify PCSProvideSimControlPanelSelectionSSFSimulation; }
    }
    verification <'VC-01.10b-T'> vcT_01_10b : VerifyByTest {
        objective { verify supportFollowingSSFAccordingARINC610RUNSIM; }
    }
    verification <'VC-01.11-T'> vcT_01_11 : VerifyByTest {
        objective { verify PCSProvideNavigationControlsPanelSettingAutopilotTargets; }
    }
    verification <'VC-02.01-T'> vcT_02_01 : VerifyByTest {
        objective { verify tactical2DMapFetchRenderOpenStreetMapTilesCorrespondingAircraftS; }
    }
    verification <'VC-02.01-I'> vcI_02_01 : VerifyByInspection {
        objective { verify tactical2DMapFetchRenderOpenStreetMapTilesCorrespondingAircraftS; }
    }
    verification <'VC-02.03-T'> vcT_02_03 : VerifyByTest {
        objective { verify PCSReceiveThreatDetectionsIncomingSyntheticEnvironment; }
    }
    verification <'VC-02.03b-T'> vcT_02_03b : VerifyByTest {
        objective { verify tactical2DMapDisplayThreatDetectionsCommunicatedPCSScaledColor; }
    }
    verification <'VC-02.04-T'> vcT_02_04 : VerifyByTest {
        objective { verify PCSDisplayGroundProximityAttentionGetterEG; }
    }
    verification <'VC-03.01-T'> vcT_03_01 : VerifyByTest {
        objective { verify compriseSyntheticEnvironmentSimulationExternalEntitiesSimulatedScenario; }
    }
    verification <'VC-03.02-T'> vcT_03_02 : VerifyByTest {
        objective { verify syntheticEnvironmentProvideInterfaceGUISpawnClassifyFRIEND; }
    }
    verification <'VC-03.03-T'> vcT_03_03 : VerifyByTest {
        objective { verify syntheticEnvironmentGUIAllowInstructorSetAdjustBeacon; }
    }
    verification <'VC-03.04-T'> vcT_03_04 : VerifyByTest {
        objective { verify syntheticEnvironmentGUIAllowInstructorSetAdjustOwnship; }
    }
    verification <'VC-03.05-T'> vcT_03_05 : VerifyByTest {
        objective { verify syntheticEnvironmentComputeBeaconSDetectionStatusEvaluating; }
    }
    verification <'VC-04.01-T'> vcT_04_01 : VerifyByTest {
        objective { verify busManagerOrchestrateExchangeStateVariablesBetweenTacticalDatabus; }
    }
    verification <'VC-05.01-D'> vcD_05_01 : VerifyByDemonstration {
        objective { verify integrateFlightGearCOTSFlightSimulatorOTWVisualEngine; }
    }
    verification <'VC-05.02-D'> vcD_05_02 : VerifyByDemonstration {
        objective { verify integrateOpenStreetMapTileServiceTactical2DMap; }
    }
}
